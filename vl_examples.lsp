(defun  c:mkdir-tree ( / i new_str )
    (setq name_folder "tree")
    (vl-mkdir name_folder)
    (setq folders 5)
     (setq i 0)
     (while (< i  folders)
          (setq name_folder (strcat "tree\\" (itoa i) ))
          (vl-mkdir (strcat "tree\\" (itoa i) ))
          (setq i (+ i 1))
    )
 )
